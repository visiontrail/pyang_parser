module certus-5gnr-types-for-du {
    namespace "http://certusnet.com/5gnr/certus-5gnr-types-for-du";
    prefix cgtfd;

    import ietf-inet-types { prefix inet; }
    
    organization "CertusNet";
    description "This module defines types used by 5gnr du.";
    
    revision 2019-07-08 {
        description  "Initial revision.";
    }
    
    typedef ip-version-e {
        type enumeration {
            enum IPV4;
            enum IPV6;
        }
    }
    typedef ns-agent-type-e {
        type enumeration {
            enum NS-DISABLED;
            enum NS-OAM-BASED;
            enum NS-SLICEMGR-BASED;
        }
    }
    typedef du-module-id-e {
        type enumeration {
            enum DU-NS-AGENT;
            enum OAM-AGENT;
            enum DU-MGR;
            enum DU-RRM;
            enum APP-UE;
            enum F1AP;
            enum SCTP;
            enum EGTPU;
            enum UDP;
            enum NRUP;
            enum RRC-CODEC;
            enum COMMON-CODEC;
            enum COMMON;
            enum FAST-PKT;
        }
    }
    typedef ngp-module-id-e {
        type enumeration {
            enum NGP { description 0xFFFF0000; }
            enum MEM { description 0x1000; }
            enum BUF { description 0x1001; }
            enum STATS { description 0x1002; }
            enum TIMER { description 0x1003; }
            enum STHREAD { description 0x1004; }
            enum CTHREAD { description 0x1005; }
            enum SYS { description 0x1006; }
            enum EXCP { description 0x1007; }
            enum COMM { description 0x1008; }
            enum SCTP { description 0x1009; }
            enum UDP { description 0x100A; }
            enum TCP { description 0x100B; }
            enum MSGQ { description 0x100C; }
            enum PRIOQ { description 0x100D; }
            enum WORKQ { description 0x100E; }
            enum PERF { description 0x100F; }
            enum HTTP2 { description 0x1010; }
            enum THR_POOL { description 0x1011; }
        }
    }
    typedef log-lvl-e {
        type enumeration {
            enum LL-OFF;
            enum LL-FATAL;
            enum LL-ERROR;
            enum LL-WARN;
            enum LL-INFO;
            enum LL-TRACE;
        }
    }
    
    grouping ip-addr {
        leaf ip-version { type ip-version-e; }
        leaf ipv4-addr {
            if-feature optional;
            type inet:ipv4-address;
        }
        leaf ipv6-addr {
            if-feature optional;
            type inet:ipv6-address;
        }
    }
}
