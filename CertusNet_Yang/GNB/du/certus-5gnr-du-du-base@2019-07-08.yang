submodule certus-5gnr-du-du-base {
    belongs-to certus-5gnr-du-du {
        prefix cgdu;
    }
    
    import tailf-common { prefix tailf; }
    import certus-5gnr-types-for-du {
        prefix cgtfd;
        revision-date 2019-07-08;
    }
    
    organization "CertusNet";
    description "This module defines du base configuration.";
    
    revision 2019-07-08 {
        description "Initial revision.";
    }


    grouping sctp {
        container dst {
            uses cgtfd:ip-addr;
            leaf port { type uint32; }
        }
        container src {
            uses cgtfd:ip-addr;
            leaf port { type uint32; }
        }
        container cfg-params {
            leaf num-outbound-streams { type uint16; }
            leaf max-inbound-streams { type uint16; }
            leaf max-init-attempts { type uint16; }
            leaf hb-interval { type uint16; }
            leaf max-path-retx { type uint16; }
        }
    }
    grouping drx {
        leaf inactivity-tmr {
            type uint32;
            default 4;
        }
        leaf retx-tmr-dl {
            type uint32;
            default 4;
        }
        leaf retx-tmr-ul {
            type uint32;
            default 4;
        }
        leaf long-cycle {
            type uint32;
            default 0;
        }
        leaf short-cycle {
            type uint32;
            default 3;
        }
        leaf short-cycle-tmr {
            type uint32;
            default 2;
        }
    }
    grouping log {
        leaf file-name {
            type string;
            default "du";
        }
        list du-modules {
            key module-id;
            leaf module-id { type cgtfd:du-module-id-e; }
            leaf log-lvl {
                type cgtfd:log-lvl-e;
                default LL-OFF;
            }
        }
        list ngp-modules {
            key module-id;
            leaf module-id { type cgtfd:ngp-module-id-e; }
            leaf log-lvl {
                type cgtfd:log-lvl-e;
                default LL-OFF;
            }
        }
    }


    grouping du-base {
        leaf gnb-du-id {
            type uint64;
            tailf:validate "gnb-du-id-check" {
                tailf:dependency ".";
            }
        }
        leaf gnb-du-name {
            if-feature optional;
            type string;
        }
        leaf max-cell-supported {
            type uint8;
            default 1;
        }
        container ue {
            leaf max-ue-supported { type uint16; }
            leaf rnti-start { type uint16; }
            leaf max-num-rnti { type uint16; }
        }
        container sctp {
            uses sctp;
        }
        container egtpu {
            uses cgtfd:ip-addr;
            leaf teid-min { type uint32; }
            leaf teid-max { type uint32; }
        }
        container f1u-flow-ctrl {
            leaf max-rlc-sdu-q-size { type uint16; }
            leaf rlc-sdu-q-lwr-thr { type uint16; }
            leaf rlc-sdu-q-upr-thr { type uint16; }
            leaf nrup-flw-ctrl-tmr { type uint16; }
            leaf en-nrup_missing_rept { type empty; }
            leaf read-ingress-pkts-per-tti { type uint32; }
        }
        container drx {
            if-feature optional;
            uses drx;
        }
        container log {
            uses log;
        }
    }
}
