module certus-5gnr-du-du {
    namespace "http://certusnet.com/5gnr/du/certus-5gnr-du";
    prefix du;
    
    include certus-5gnr-du-du-base {
        revision-date 2019-07-08;
    }
    include certus-5gnr-du-du-ns {
        revision-date 2019-07-08;
    }
    
    revision 2019-07-08 {
        description "Initial revision.";
    }


    container du {
        container base { uses du-base; }
        container ns { uses ns; }
    }
}
