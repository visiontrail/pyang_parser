submodule certus-5gnr-du-cell-base {
    belongs-to certus-5gnr-du-cells {
        prefix cgdcs;
    }
    
    import tailf-common {
        prefix tailf;
    }
    import certus-5gnr-types-for-cell {
        prefix cgtfc;
        revision-date 2019-06-20;
    }
    
    organization "CertusNet";
    description "This module defines du cell base configuration.";
    
    revision 2019-06-20 {
        description  "Initial revision.";
    }

    grouping s-nssai {
        leaf sst {
            type cgtfc:sst-t;
            description 'Slice/Service Type';
        }
        leaf sd {
            type cgtfc:sd-t;
            description "Slice Differentiator";
        }
    }
    grouping served-plmn {
        uses cgtfc:plmn-id;
        list s-nssais {
            key sst;
            uses s-nssai;
            max-elements 1024;
            description "Single Network Slice Selection Assistance Information";
        }
    }
    

    grouping cell-base {
        leaf nr-mode-type { type cgtfc:nr-mode-type-e; }
        container nr-cgi {
            uses cgtfc:plmn-id;
            leaf nr-cell-id {
                type cgtfc:nr-cell-id-t;
                tailf:validate "nr-cell-id-check" {
                    tailf:dependency ".";
                }
            }
            description "NR Cell Global Identifier";
        }
        leaf nr-pci {
            type cgtfc:nr-pci-t;
            description "NR Physical Cell ID (0..1007)";
        }
        leaf tac-5gs {
            type cgtfc:tac-5gs-t;
            description "5GS Tracking Area Code";
        }
        leaf cfgrd-eps-tac {
            type cgtfc:cfgrd-eps-tac-t;
            description "Configured EPS TAC";
        }
        list served-plmns {
            key "mcc mnc";
            uses served-plmn;
            min-elements 0;
            max-elements 6;
        }
        container si-perd {
            leaf sib2-perd {
                if-feature optional;
                type cgtfc:si-perd-e;
            }
            leaf sib3-perd {
                if-feature optional;
                type cgtfc:si-perd-e;
            }
            description "SI Periodicity";
        }
    }
}
