submodule certus-5gnr-du-cell-l1 {
    belongs-to certus-5gnr-du-cells {
        prefix cgdcs;
    }

    import tailf-common {
        prefix tailf;
    }
    import certus-5gnr-types-for-cell {
        prefix cgtfc;
        revision-date 2019-06-20;
    }

    organization "CertusNet";
    description "This module defines du cell L1 configuration.";
    
    revision 2019-06-20 {
        description  "Initial revision.";
    }
    
    grouping plmn-id-info {
        list plmn-ids {
            key "mcc mnc";
            uses cgtfc:plmn-id;
            min-elements 1;
            max-elements 6;
        }
        leaf nr-cell-id {
            type cgtfc:nr-cell-id-t;
            tailf:validate "nr-cell-id-check" {
                tailf:dependency ".";
            }
        }
        leaf tac {
            if-feature optional;
            type uint32;
            description "Tracking Area Code";
        }
        leaf ranac {
            if-feature optional;
            type uint8 { range "0..255"; }
            description "RAN Area Code";
        }
        leaf cell-rsrvd-for-operator-use {
            type empty;
            description "Cell Reserved For Operator Use";
        }
    }
    
    
    grouping cell-sel-info {
        leaf q-rx-lvl-min {
            if-feature optional;
            type cgtfc:q-rx-lvl-min-t;
            description "Minimum Received RSRP Level";
        }
        leaf q-rx-lvl-min-offset {
            if-feature optional;
            type uint8 { range "1..8"; }
            description "Minimum Received RSRP Level Offset";
        }
        leaf q-rx-lvl-min-sul {
            if-feature optional;
            type cgtfc:q-rx-lvl-min-t;
            description "Minimum Received RSRP Level Of SUL";
        }
        leaf q-qual-min {
            if-feature optional;
            type cgtfc:q-qual-min-t;
            description "Minimum Received RSRQ Level";
        }
        leaf q-qual-min-offset {
            if-feature optional;
            type uint8 { range "1..8"; }
            description "Minimum Received RSRQ Level Offset";
        }
    }
    grouping cell-access-info {
        list plmn-id-infos {
            key nr-cell-id;
            uses plmn-id-info;
            
            min-elements 1;
            max-elements 6;
        }
        leaf cell-rsrvd-for-other-use {
            type empty;
            description "Cell Reserved For Other Use";
        }
    }
    grouping ue-timers {
        leaf t300 { type cgtfc:t300-e; }
        leaf t301 { type cgtfc:t301-e; }
        leaf t310 { type cgtfc:t310-e; }
        leaf n310 { type cgtfc:n310-e; }
        leaf t311 { type cgtfc:t311-e; }
        leaf n311 { type cgtfc:n311-e; }
        leaf t319 { type cgtfc:t319-e; }
    }
    

    grouping prach {
        leaf root-seq-idx {
            type uint16 { range "0..837"; }
        }
        leaf cfg-idx { type uint8; }
        leaf zero-correlation-zone-cfg {
            type uint8 { range "0..15"; }
        }
        leaf restricted-set {
            if-feature optional;
            type uint8;
        }
        leaf freq-start {
            type uint16 { range "0..274"; }
            default 0;
        }
        leaf freq-offset {
            type uint8 { range "0..94"; }
            default 0;
        }
        leaf scs { type cgtfc:scs-e; }
        leaf fdm { type cgtfc:msg1-fdm-e; }
        leaf ssb-per-rach-occ {
            type cgtfc:ssb-per-rach-occ-e;
            description "SSBs Number Per RACH Occasion";
        }
    }
    grouping mib {
        leaf scs-cmn {
            type cgtfc:scs-cmn-e;
            description "Subcarrier Spacing Common";
        }
        leaf ssb-sc-offset {
            type cgtfc:ssb-sc-offset-t;
            default 0;
            description "SSB Subcarrier Offset";
        }
        container pdcch-cfg-sib1 {
            leaf coreset-zero {
                type cgtfc:coreset-zero-t;
                description "Control Resource Set With ID #0";
            }
            leaf ss-zero {
                type cgtfc:ss-zero-t;
                description "Search Space With ID #0";
            }
        }
        leaf cell-barred { type empty; }
        leaf intra-freq-resel {
            type empty;
            description "Intra Frequency Reselection";
        }
    }
    grouping sib1 {
        container cell-sel-info {
            uses cell-sel-info;
        }
        container cell-access-info {
            uses cell-access-info;
        }
        container ue-timers {
            uses ue-timers;
        }
    }
    
    
    grouping cell-l1 {
        leaf dl-central-freq {
            type uint32;
            description "DL Central Frequency";
        }
        leaf ul-central-freq {
            type uint32;
            description "UL Central Frequency";
        }
        leaf ca-lvl {
            type uint8;
            default 0;
            description "Cell Aggregation Level";
        }
        container prach {
            if-feature optional;
            uses prach;
        }
        container mib {
            uses mib;
        }
        container sib1 {
            uses sib1;
        }
    }
}
