module egtpuConfig {
   namespace "http://tail-f.com/ns/example/egtpuconfig";
   prefix egtpuConfig;
   
   import ietf-inet-types {
	   prefix inet;
   }

   grouping egtpuTransportConfigParams {
      leaf ipAddress {
            type inet:ipv4-address;
            default "192.168.200.101";
            description "This contains ip address";
      }

      leaf teidMin {
         type uint32 {
             range 0..4294967295 {
                 error-message "Value should be in the range of [0,4294967295]";
             }
         }
         description "This contains minimum teid value";
         must ". <= ../teidMax" {
            error-message "Teid min should be less than or equal ot Teid Max";
         }      
         default 1;
      }

      leaf teidMax {
         type uint32 {
             range 0..4294967295 {
                 error-message "Value should be in the range of [0,4294967295]";
             }
         }
         description "This contains maximum teid value";
         must ". >= ../teidMin" {
             error-message "Teid max should be greater than or equal ot Teid Min";
         } 
         default 100;
      }
      
   }

   grouping egtpuConfigType {
      container f1UEgtpuTransportConfig {
         uses egtpuTransportConfigParams;
         description "This contains the f1 u egtpu transport layer configuration";
      }
   }
}
