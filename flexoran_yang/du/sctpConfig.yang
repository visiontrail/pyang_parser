module sctpConfig {
   namespace "http://tail-f.com/ns/example/sctpconfig";
   prefix sctpConfig;

   import tailf-xsd-types {
      prefix xs;
   }

   import ietf-inet-types {
      prefix inet;
   }

   grouping sctpConfigType {

      leaf numOutBoundStreams {
         //type uint16;  //Ritesh: Range check
         type uint16 {
            range 0..255 {
               error-message "Value should be in the range of [0,255]";
            }
         }
         description "Number of outbound streams";
         must ". != '0' " {
            error-message "out bound stream number should not be 0";
         }
         default 1;
      }

      leaf maxInboundStreams {
         //type uint16;   //Ritesh: Range check 
         type uint16 {
             range 0..255 {
                 error-message "Value should be in the range of [0,255]";
             }
         }
         description "The gNB-DU ID is independently configured from cell identifiers, i.e. no connection between gNB-DU ID and cell identifiers";
         must ". != '0' " {
            error-message "max in bound stream number should not be 0";
         }
         default 1;
      }

      leaf maxInitAttempts {
         type uint16 {
            range "1..30" {
               error-message "attempts should be in range 1 to 30";
            }
         }
         description "This contains maximum number of attempts";
         default 5;
      }

      leaf hbInterval {
         type uint16 {
            range "0..60" {
               error-message "value should be in range 0 to 60 milliseconds";
            }
         }
         description "This contains hb interval in Milliseconds";
         default 1;
      }

      leaf maxPathRetx {
         type uint16 {
            range "1..30" {
               error-message "value should be in range 1 to 30";
            }
         }
         default 1;
      }
   }

   grouping sctpConnConfigType {
      leaf sctpDstIpAddr {
         type inet:ipv4-address;
         default "192.168.200.101";
         description "This contains destination ip address";

      }

      leaf sctpSrcIpAddr {
         type inet:ipv4-address;
         default "192.168.200.102";
         description "This contains source ip address";

      }

      leaf sctpDstPortNum {
         type inet:port-number;
         default "38472";
         description "This contains destination port number";
      }

      leaf sctpSrcPortNum {
         type inet:port-number;
         default "38472";
         description "This contains destination port number";
      }
   }


}
