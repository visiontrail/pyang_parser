module ngran-nRCellDU {
   namespace "http://tail-f.com/ns/example/ngran-nRCellDU";
   prefix ngran-nRCellDU;

   import nrm-types-3gpp { 
      prefix nrm-type; 
   }

   import duEnum {
      prefix duEnum;
   }
   
   import cellSubConfig {
      prefix cellSub;
   }

   grouping NRCellDU {
      list NRCellDU {
         key "nCI";
         leaf nCI {
            config "true";
            description "It uniquely identifies a NR cell within a PLMN."; 
            reference "See NR Cell identifier (NCI) subclause 8.2 of 3GPP TS 38.300 [3].";
            type nrm-type:t_NCI;
         }

         leaf AdminState {
            type enumeration {
               enum BLOCKED;
               enum UNBLOCKED;
            }
            default UNBLOCKED;
            description "Admininstration State : Blockd or unBlockd";
         }

         list pLMNId {
            min-elements "0";
            description "a list of PLMN-Id, PLMN-Id= Mobile Country Codes (MCC)|| Mobile Network Codes(MNC) ";
            config "true";
            key MCC;
            uses nrm-type:pLMNId;
         }

         leaf operationalState  {
            config "false";
            description "CM, It indicates the operational state of the NRCellDU instance. It describes whether the resource is installed and partially or fully operable (Enabled) or the resource is not installed or not operable (Disabled).";
            type nrm-type:t_operationalState;
         }

         leaf administrativeState  {
            description "CM, It indicates the administrative state of the NRCellDU. It describes the permission to use or prohibition against using the cell, imposed through the OAM services.";
            config "true";
            type nrm-type:t_administrativeState;
         }

         leaf cellState  {
            description "It indicates the usage state of the NRCellDU instance. It describes whether the cell is not currently in use (Idle), or currently in use but not configured to carry traffic (Inactive) or is currently in use and is configured to carry traffic (Active)";
            mandatory "true";
            config "false";
            type nrm-type:t_cellState;
         }

         leaf-list s_NSSAI {
            min-elements "0";
            config "true";
            type nrm-type:t_s_NSSAI; 
         } 

         container cellGenConfigInfo {
            leaf nRTAC {
               description "It includes Tracking Area Code";
               mandatory "true";
               config "true";
               type uint32;
            }

            list servedPlmnList {
               key "servedPlmnIndex";
               leaf servedPlmnIndex {
                  type uint8;
                  description "It includes served plmn index";
               }
               container servedPlmnId {
                  uses nrm-type:pLMNId;
               }
               list sliceList {
                  key "sliceIndex";
                  leaf sliceIndex {
                     type uint8;
                  }
                  uses cellSub:s_nssaiT;
               }

            }

            leaf modeInfo {
               type duEnum:modeInfoEnum;
               default "FDD"; 
               description "It includes mode info";
            }
            container nRCGI {
               uses cellSub:nrCgiT;
               description "This contains the NR cell global Id";
            }
            leaf nRPCI {
               description "It includes nr pci value";
               mandatory "false";
               config "true";
               type nrm-type:t_nRPCI;
               default 1;
            }

            leaf subCarrierSpacing {  
                type duEnum:scsEnum;
                must " . = 'scs_KHz15' or" + " . = 'scs_KHz30' or " + " . = 'scs_KHz120'" {
                    error-message "As per spec, only 15 and 30 for FR1 and 120 for FR2:depends on freqRangeType";
                }
                default scs_KHz120;
                description "It includes sub carrier spacing value";  
            }
            leaf freqRangeType {
               type duEnum:freqRangeTypeEnum;
               default "freqRangeType_FR2";
               description "This contains the frequency range type";
            }
         }
         container macConfigCommon {

            leaf maxUlUePerTTI {
               type uint8 { 
                  range "1..16" {
                     error-message "Value Should be in Between 1 to 16.";    
                  }                                                   
               }
               default "1";
               description "It includes maximum UE per uplink slot";
            }
            leaf maxDlUePerTTI {
               type uint8 { 
                  range "1..16" {
                     error-message "Value Should be in Between 1 to 16.";    
                  }                                                   
               }
               default "1";
               description "It includes maximum UE per downlink slot";
            }
            leaf maxDlHqTX {
               type uint8 { 
                  range "1..15" {
                     error-message "Value Should be in Between 1 to 15.";    
                  }                                                   
               }
               default "1";
               description "This contains the maximum DL hqra transmission";
            }
            leaf maxMsg4HqTx {
               type uint8 { 
                  range "1..15" {
                     error-message "Value Should be in Between 1 to 15.";    
                  }                                                   
               }
               default "1";
               description "This contains the maximum MSG4 harq transmission";
            }
            leaf prmblStart {
               type uint8 { 
                  range "0..63" {
                     error-message "Value Should be in Between 0 to 63.";    
                  }                                                   
               }
               default "47";
               description "This contains the preamble start";
            }
            leaf prmblSize {
               type uint8 { 
                  range "0..63" {
                     error-message "Value Should be in Between 0 to 63.";    
                  }                                                   
               }
               default "4";
               description "This contains the preamble size";
            }
            leaf cFI {
               type uint32 {
                  range "1..14" {
                     error-message "cFI value should be between 1 to 14";
                  }
               }
               must ". = '1' or " + ". = '2' or " + ". = '3'" {
                  error-message "cFI value shuold be one of 1,2,3";
               } 
               default "2";
               description "This contains the frequency configuration";
            }
            leaf cyclicPrefix {
               type duEnum:cyclicPrefixEnum;
               default "cyclicPrefix_NORMAL";
               description "This contains the cyclic prefix enum value";
            }
            leaf dmrsTypaPos {
               type duEnum:dmrsTypAPosEnum;
               default "dmrsTypAPos_pos2";

               description "This contains dmrs Type A position";
            }
            leaf maxNumUEs {
               type uint8 {
                  range "1..64" {
                     error-message "Value should be in between 1 to 64";
                  }
               }
               default "8";
               description "This contains the maximum number of UEs";
            }
            leaf csiPrdcty {
               type uint8;
               must ". = '4' or " + ". = '5' or " + ". = '8' or " + ". = '10' or " + ". ='16' or " + ". = '20' or " + ". ='40' or " + ". = '80' or " + ". = '160' or " + ". = '320' " {
                  error-message "Value Should be one of 4,5,8,10,16,20,40,80,160,320."; 
               }
               default "160";
               description "This contains the csi periodicity";
            }

            leaf nrUEMaxDlRank {
               type uint8 {
                  range "1..4" {
                     error-message "Value should be 1  to 4";
                  }  
               }
               default 4;
               description "This contains the nr UE max downlink rank";
            }
            leaf nrUEPtrsEnable {
               type boolean;
               default true;
               description "This shows nr UE ptrs is present or not";
            }
            leaf nrUEMaxUlRank {
               type uint8 {
                  range "1..4" {
                     error-message "Value should be 1  to 4";
                  }  
               }
               default 4;
               description "This contains the nr UE max uplink rank";
            }
            leaf nrDlNumOfAntPorts {
               type uint8 {
                  range "1..4" {
                     error-message "Value should be 1,2,4";
                  }  
               }
               must " .  != '3'" {
                  error-message "3 is not a valid value , choose a value between 1,2,4";
               }
               default 4;
               description "This contains the nr downlink number of anti ports";
            }
            leaf ulModulation5Gnr { 
               type duEnum:mcsTblEnum;
               default MCS_TBL_64QAM;
               description "This contains the 5gnr modulation value";
            }
            leaf dlModulation5Gnr {
               type duEnum:mcsTblEnum;
               default MCS_TBL_64QAM;
               description "This contains the 5gnr modulation value";
            }
            leaf schDlMcs {
               type uint8 {
                  range "0..31" {
                     error-message "Value should be 0-31";
                  }  
               }
               default 28;
               description "This contains the downlink mcs scheduled value";
            }
            leaf schUlMcs {
               type uint8 {
                  range "0..31" {
                     error-message "Value should be 0-31";
                  }  
               }
               default 28;
               description "This contains the uplink mcs scheduled value";
            }


         }
         container tddUlDlConfigurationCommon {  //TOD:P4 Genreal comment: change long names in smaller ones
            leaf slotFormat {
               type uint8 { 
                  range "0..8" {   //TODO:P1 make it enum Res: cell_config1.txt Santosh What would be other values
                     //TODO:P4 It should define the RRC slotConfig where we define the slot duration and number of symbols within a slot.
                     error-message "Valuse should be in between 0 to 8" ;
                  }
               }
               default "3";
               description "This contains slot format";
            }
         }
         container DownlinkConfigCommon {
            list dlBwpCfg {
               key "bwpId";
               max-elements 4;
               leaf bwpId {
                  type uint8;

               }
               uses cellSub:dlBwpConfigT;
               description "This contains DL bwp configuration";
            }
            container dlFreqInfo {
               uses cellSub:gnbDuFreqInfoDlCfgT;
               description "This contains DL frequency information";
            }
         }
         container UplinkConfigCommon {
            list ulBwpCfg{
               key "bwpId";
               max-elements 4;
               leaf bwpId {
                   type uint8 {
                       range "0..4" {
                           error-message "bwpId should be in range [0,4]";
                       }
                   }
               }
               uses cellSub:ulBwpConfigT;
               description "This contains UL bwp ocnfiguration"; 
            }
            container ulFreqInfo {
                uses cellSub:gnbDuFreqInfoUlCfgT;
                description "This contains UL frequency information";
            } 
         }
         container supplementaryUplinkConfigCommon {
            leaf sulCfgPres {
               type boolean;
               default "false";
               description "SUL configuration presence";
            }
            //TODO:P1 rest all should be depend upon value of sulCfgPres
            leaf maxUlUePerTTI{ //TODO:P1 maxulpertti
                  type uint8 {
                     range 1..16 {
                        error-message "Value should be in range [1,16]";
                     }
                  }
               default "1";
               description "This contains max UE per slot";
            }
            leaf isHarmoniceNB { //TODO:p1 check for the duplicate with sulharmonic in du model
               type boolean;
               default "false";
            }
            leaf isSulFreqMute {
               type boolean;
               default "true";
               description "This contains SUL frequency mute status";
            }
            leaf cCCHcqi {
                  type uint8 {
                     range 1..15 {
                        error-message "Value should be in range [1,15]";
                     }
                  }
               default "1";
               description "Common control channel quality indicator";
            }
            container FreqCfgUl {
               uses cellSub:gnbDuFreqInfoUlCfgT;
               description "This contains UL frequency configuration";
            }
            container TgtUlCqi {
               uses cellSub:UlTrgCqiCfgT;
               description "Target UL Cqi";
            }

            list SULbWPcFGg {   //TODO:p1 Make it as per convention
               key "bwpId";
               max-elements 4;
               leaf bwpId {
                   type uint8 {
                       range "0..4" {
                           error-message "bwpId should be in range [0,4]";
                       }
                   }
                   description "This contain bandwidth part id";
               }
               uses cellSub:ulBwpConfigT;
               description "This contains SUL bwp configuration";

            }
         }
         container si-SchedulingInfo {

            leaf sib2Present {
               type boolean;
               default "true";
               description "This contains sib2 rpesent or not";
            }

            leaf sib3Present {
               type boolean;
               default "true";
               description "This contains sib3 rpesent or not";
            }

            leaf sib2Perd {
               when "../sib2Present = 'true'";
               type duEnum:sibT;
               default "sibT_rf128";
               description "This contains sib2 value";
            }

            leaf sib3Perd {
               when "../sib3Present = 'true'";
               type duEnum:sibT;
               default "sibT_rf256";
               description "This contains sib3 value";
            }

            list sibs {
               key "valueTag";
               max-elements 32;
               leaf valueTag {      //TODO:p4 Libin check for Value tag
                  type uint8 {
                     range 0..31 {
                        error-message "Value should be in range [0,31]";
                     }
                  }
               }
               leaf sibType {
                  type duEnum:sibTypeEnum;
                  default "sibType_DU_SIB_TYPE_2";
                  description "This contains types of sib";
               }
            }
         }
         container l1-CfgInfo{           //TODO:p4 we need to remove this and derive it form cell config params
            //TODO: avoid derivacle params

            leaf nDLcentrFreq{         
               type uint32 {
                  range "450000..52600000" {
                     error-message "Value Should be in between 450000 to 52600000";
                  }
               }
               default "28015680";
               description "This contains downlink center frequency";
            }

            leaf nULcentrFreq {
               type uint32 {
                  range "450000..52600000" {
                     error-message "Value Should be in between 450000 to 52600000";
                  }
               }
               default "28015680";
               description "This contains uplink center frequency";
            }

            leaf nDLbandwith{
               type uint16 {
                  range "5..400" {
                     error-message "Value Should be in between 5 to 400";
                  }
               }
               default "100";
               description "This contains downlink bandwidth";
            }

            leaf nULbandwith {
               type uint16 {
                  range "5..400" {
                     error-message "Value Should be in between 5 to 400";
                  }
               }
               default "100";
               description "This contaons uplink bandwidth";
            }

            leaf nSSBpwr {
               type int32 {
                  range "-60..50" {
                     error-message "Value Should be in between -60 to 50";
                  }
               }
               default "50";
               description "This contains ssb power";
            }

            leaf nSSBprbOffset {
               type uint8 {
                  range "0..255" {
                     error-message "Value Should be in between 0 to 255";
                  }
               }
               default "0";
               description "This contains SSB PRB offset";
            }

            leaf nDLFftSize {
               type uint32;
               must ". = '512' or " + ". = '1024' or " + ". = '2048' or " + " . = '4096'" {
                  error-message "Value Must be one of 512,1024,2048,4096";
               }
               default "1024";
               description "This contains downlink fft size";
            }

            leaf nULFftSize{
               type uint32;
               must ". = '512' or " + ". = '1024' or " + ". = '2048' or " + " . = '4096'" {
                  error-message "Value Must be one of 512,1024,2048,4096";
               }
               default "1024";
               description "This contains uplink fft size";
            }

            leaf nCAlevel{
               type uint8 {
                  range "0..5" {
                     error-message "Value Should be in range [0,5]";
                  }
               }
               default "0";
            }

            leaf nDLCarrier-K0{
               type uint8 {
                  range "0..2" {
                     error-message "Value Should be in between 0 to 2";
                  }
               }
               default "1";
               description "This contains Carrier aggregation level";
            }

            leaf nULCarrier-K0 {
               type uint8 {
                  range "0..2" {
                     error-message "Value Should be in between 0 to 2";
                  }
               }
               default "1";
               description "This contains Downlink carrier K0";
            }

            container prachCfg {
               uses cellSub:l1PrachCfgInfoT;
               description "This contains rach configuration0";
            }

            container mibParams {
               uses cellSub:mibParamsT;  //TODO:p2 verify the mib filling in appl and remove the calculated params
               description "Master information block configuration";
            }

            container sib1Params {
               uses cellSub:sib1ParamsT;
               description "System information block configuration";
            }
         }

         container trafficPattern {
            uses cellSub:ltenrCoTraficPatternTypeT;
         }
         container s_NSSAIRan {
            uses cellSub:nsCfgInfoT;
         }
         container pCCHcfgInfo {

            leaf defaultPagCycle {
               type duEnum:defaultPagCycleEnum;
               default "defaultPagCycle_rf64";
               description "Common channel configuration ";
            }
            leaf paging_value_n { 
               type duEnum:paging_value_nEnum;
               default PAGING_DURATION_ONE_T;
               description "It contains pagging value";
            }

            leaf ns {
               type duEnum:nsEnum;
               default "ns_four";
               description "It contains ns value";
            }


            leaf firstPDCCHmonitoringPres {
               type boolean;
               default "false";
               description "It shows first pdcch monitoring present or not";
            }

            container PDCCHmonitoringInfo {
               when "../firstPDCCHmonitoringPres = 'true'"; 
               uses cellSub:firstPdcchMonitoringInfoT;
            }


         }
         container DrxInfo {

            leaf isDrxEnabled {
               type boolean;
               default "true";
               description "This contains DRX present or not";
            }

            //TODO:p1 Rest all should depend on value of isDrxEnabled

            leaf isDrxOnDurationTmrType {
               type duEnum:isDrxOnDurationTmrTypeEnum;
               default "drx-onDurationTimerMilliSeconds";
               description "DRX on duration timer type is presence";
            }

            leaf DrxInactivityTmr {
               type duEnum:inactivityTmrEnum;
               default DRX_TMR_PRD_4MS;
               description "This conatins DRX inactivity timer";
            }

            leaf DrxOnDurationTmr {
               type duEnum:drxOnDurationTmrEnum;
               default DRX_ON_DURATION_TMR_PRD_1MS ;
               description "This contains DRX on duration timer";
            }

            leaf DrxRttTmrDl {   //TODO:p4 rename it as drx-HQ-RTT-TmrDL
               type uint8 {
                  range "0..56" {
                     error-message "DRX RTT timer for DL should be between 0 to 56";
                  }
               }
               default "56";
               description "This conatins DRX RTT timer for DL";
            }

            leaf DrxRttTmrUl{
               type uint8 {
                  range "0..56" {
                     error-message "DRX RTT timer for UL should be between 0 to 56";
                  }
               }
               default "56";
               description "This conatins DRX RTT timer for UL";
            }

            leaf DrxRetxTmrDl {
               type duEnum:drxRetxTmrInSlotEnum;
               default SLOT_DRX_TMR_PRD_4Slot;
               description "DRX re-transmission timer for DL";
            }

            leaf DrxRetxTmrUl{
               type duEnum:drxRetxTmrInSlotEnum;
               default SLOT_DRX_TMR_PRD_4Slot;
               description "DRX re-transmission timer for UL";
            }

            leaf DrxLongCycle {
               type duEnum:DrxLongCycleEnum;
               default DRX_CYCL_PRD_10MS; 
               description "This contains DRX long cycle time";
            }

            leaf DrxCycleStartOffset {
               type uint32 {
                  range "0..10239" {
                     error-message "DRX cycle start offset should be between 0 to 10239";
                  }
               }
               default "0";
               description "DRX cycle start offset";
            }

            leaf isDrxShortCycleEnabled {
               type boolean;
               default "true";
               description "This contains DRX short cycle present or not";
            }

            leaf DrxShortCycleTmr {
               when "../isDrxShortCycleEnabled = 'true'"; 
               type uint32 {
                  range 1..16 {
                     error-message "Value should be in range [1,16]";
                  }
               }
               default "2";
               description "This contains DRX short cycle timer";
            }

            leaf DrxSlotOffset{
               type uint8 {
                  range 0..31 {
                     error-message "Value Should be in range[0,31]";
                  }
               }
               default "0";
               description "This contains DRX slot offset";
            }

         }

         container cellPfsCfgInfo {
            //TODO:p1 Check with santosh kula for range and default values
            leaf nr5qiCoeff {
               type uint16 {
                  range 0..100 {
                     error-message "Value should be in the range of [0,100]";
                  }
               }
               default 5;
            }
            leaf gbrServedRateCoeff {
               type uint16 {
                  range 0..100 {
                     error-message "Value should be in the range of [0,100]";
                  }
               }
               default 5;
            }
            leaf uePfsCoeff { 
               type uint16 {
                  range 0..100 {
                     error-message "Value should be in the range of [0,100]";
                  }
               }
               default 5;
            }
            leaf totalSlicePrioLevels {
               type uint16;
               must ". = '10'" {
                  error-message "totalSlicePrioLevels Must be 10";
               }
               default 10;
            }
            leaf totalUeServedRatePrioLevels {
               type uint16;
               must ". = '100'" {
                  error-message "totalUeServedRatePrioLevels Must be 100";
               }
               default 100;
            }
            leaf totalGbrServedRatePrioLevels {
               type uint16;
               must ". = '100'" {
                  error-message "totalGbrServedRatePrioLevels Must be 100";
               }
               default 100;
            }
            leaf throughputCoeff {
               type uint32 {
                  range "0..10" {
                     error-message "throughputCoeff value should be in range [0,10]";
                  }
               }
               default 5;
            }
            leaf fairnessCoeff {
               type uint32 {
                  range "0..10" {
                     error-message "fairnessCoeff value should be in range [0,10]";
                  }
               }
               default 5;
            }

         }

         container pdschRateMatching {
            leaf ssPbchEnabled {
               type boolean;
               default false;
            }
            leaf coreSetEnabled {
               type boolean;
               default false;
            }
         }


      }
   }
}
