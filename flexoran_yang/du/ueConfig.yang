module ueConfig {
   namespace "http://tail-f.com/ns/example/ueconfig";
   prefix ueconfig;

   grouping ueConfigType {

      leaf rntiStart {
         type uint16 {
            range "0..65535" {
               error-message "rntiStart should be between 0 and 65535";
            }
         }
         description "This contains starting RNTI value";
         default 17017;
      }

      leaf maxNumRnti {
         type uint16 {
            range "0..256" {
               error-message "maxNumRntis should be between 0 and 256";
            }
         }
         description "This contains maximum number of rnti";
         default 256;
      }

      leaf maxNumUes {
         type uint16 {
            range "1..64" {
               error-message "UEs should be between 1 and 64";
            }
         }
         description "This contains maximum number of UEs";
         default 8;
      }

   }
}
