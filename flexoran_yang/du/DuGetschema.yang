module DuGetschema {
    namespace "http://certusnet.com.cn/flexoran/du/DuGetschema";
    prefix duschema;
    
    organization "CertusNet";
    description "This module defines du module ID.";
    
    typedef  du-module-id-e {
        type enumeration {
            enum LIB-YANG { value 0; }
            enum LIB-SSH { value 1; }
            enum LIB-NETCONF { value 2; }
            enum OAM-LOGGER { value 10; }
            enum OAM-RRU-AGENT-MANAGER { value 11; }
            enum OAM-SWM { value 12; }
            enum MODULE-INVALID { value 65535; }
        }
    }
}
