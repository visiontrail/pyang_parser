module ngran-gNBDUFunction {

   namespace "http://tail-f.com/ns/example/ngran-gNBDUFunction";
   prefix ngran-gNBDUFunction;

   import tailf-common {
      prefix tailf;
   }
    
    import duEnum {
       prefix duEnum;
    }
   
   import ngran-nRCellDU {
      prefix NRCellDU;
   }


   import sctpConfig {
      prefix sctpConfigType;
   }

   import ietf-inet-types {
      prefix inet;
   }

   import ueConfig {
      prefix ueconfig;
   }

   import egtpuConfig {
      prefix egtpuConfigType;
   }

   import loggingConfig {
      prefix logging;
   }

   import f1uFlowCtrlCfgInfo {
      prefix f1uFlowCtrlCfgInfoType;
   }

   import nsSysCfgVect {
      prefix nsSysCfgVectType;
   }

   

   container GNBDUFunction {
      //uses mf:ManagedFunction;
       leaf gNBId {
         description "It identifies a gNB within a PLMN. See gNB Identifier (gNB ID) of subclause 8.2 of 3GPP TS 38.300 [3]). See Global gNB ID in subclause 9.3.1.6 of 3GPP TS 38.413 [5]. ";
         mandatory "false";
         type uint32
         {
            range "0..4294967295" {
               error-message "gnbId should be in between  0..4294967295" ;
            }
         }
         default 1;
      }
 
   
      leaf gNBDUId {
         description "It uniquely identifies the DU at least within a gNB. See gNB-DU ID in subclause 9.3.1.9 of 3GPP TS 38.473 ";
         mandatory "false";
         config "true";
         type uint64 {
            range "0..68719476735" {
               error-message "gnb_DU_Id should be in range [0, 68719476735]";
            } 
         }
         default 1;
      }
      leaf gNBDUNamePresent {
         type boolean;
         default 'false';
      }
      leaf gNBDUName {
          when "../gNBDUNamePresent = 'true'";
         description "PrintableString(SIZE(1..150,))";
         mandatory "false";
         config "true";
         type string {
            length "1..150";
         }
         default "gnb01du";
      }
     leaf gNBIdLength {
         description "It indicates the number of bits for encoding the gNB ID.";
         type uint32 {
            range "22..32";
         }
         default 22;
      }      

      /* doubt  container EPf1C { uses ep-rp:EPf1C; } */

      container EP_F1 {

         container sctpConfig {
            uses sctpConfigType:sctpConfigType;
            uses sctpConfigType:sctpConnConfigType;
         }
      }

      /* what would be key if it is list 
         list EPf1U { uses ep-rp:EPf1U; } 
       */

      container EP_F1U {

         container egtpuConfig {
            uses egtpuConfigType:egtpuConfigType;
         }

         container f1uFlowCtrlCfgInfo {
            uses f1uFlowCtrlCfgInfoType:f1uFlowCtrlCfgInfoType;
         }
      }

      container loggingInfo{
         uses logging:loggingConfigType;
      }


      container du_s_NSSAI {
         uses nsSysCfgVectType:nsSysCfgVectType;
      }

      uses NRCellDU:NRCellDU; 

      container ueConfig {
         uses ueconfig:ueConfigType;
      }

      leaf sulHarmonicEnabled {
         type boolean;
         default false;
      }  

      leaf nsAgentCfgType {
          type duEnum:nsAgentCfgEnum;
          default "disableNs";
      }


      container sliceMgrCfg {

          when "../nsAgentCfgType = 'sliceMgrBasedNsCfg'";
      
          leaf duSmLocalIpAddr {
              type inet:ipv4-address;
              default "168.168.31.102";
              description "This contains destination ip address";
          }

          leaf duSmLocalPort {
              type inet:port-number;
              default "4343";
              description "This contains destination port number";
          } 

         
          leaf duSmRemoteIpAddr {
              type inet:ipv4-address;
              default "168.168.31.101";
              description "This contains source ip address";
          }

          leaf duSmRemotePort {
              type inet:port-number;
              default "4343";
              description "This contains destination port number";
          } 

          
      }
   }
}
