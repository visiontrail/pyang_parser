module flexoran-logger-cfg {
    namespace "http://certusnet.com.cn/flexoran/oam/flexoran-logger-cfg";
    prefix logger;
    
    // import flexoran-oam-modules {
    //     prefix modules;
    // }
    
    organization "CertusNet";
    description "This module defines oam logger information.";
    
    revision 2019-09-30 {
        description "Initial revision.";
    }


    typedef  log-level-e {
        type enumeration {
            enum LL-NONE;
            enum LL-ERROR;
            enum LL-WARNING;
            enum LL-INFO;
            enum LL-DEBUG;
            enum LL-TRACE;
        }
    }
    
    grouping module-log-level-limit {
        // leaf module-id { type modules:module-id-e; }
        leaf log-level-limit { type log-level-e; }
    }

    container flexoran-logger-cfg {
        leaf file-base-name { type string; }
        leaf log-count-limit { type uint32; }
        leaf fflush-interval { type uint8; }
        list module-log-level-limits {
            key module-id;
            uses module-log-level-limit;
        }
    }
}
