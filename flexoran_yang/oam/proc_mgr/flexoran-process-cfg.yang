module flexoran-process-cfg {
    yang-version 1.1;
    namespace "http://certusnet.com.cn/flexoran/oam/flexoran-process-cfg";
    prefix process;

    organization "CertusNet";
    description "This module defines process module information.";

    revision 2020-02-04 {
        description "Initial revision.";
    }

  /* 进程名称 */
  typedef process-name-id {
    type enumeration {
      enum oam_module { description 0x3100; }
      enum platform_module { description 0x3200; }
      enum phy_module { description 0x3300; }
      enum du_module { description 0x3400; }
      enum cu_module { description 0x3500; }
      enum testmac_module { description 0x3600; }	  
    }
  }

  /* 进程状态类型 */
  typedef process-status-id {
    type enumeration {
      enum PROCESS_STATUS_INITIALIZING;
      enum PROCESS_STATUS_READY;
      enum PROCESS_STATUS_FAILED;
      enum PROCESS_STATUS_NOTINSTALLED;
      enum PROCESS_STATUS_INVALID;
   
    }
  }

  // Radisys <--> OAM 进程状态消息
  grouping process-oam-msg {
    list process-msgs {
      description
        "process status message";
      key "process-name";

      leaf process-name {
        type process-name-id;
      }

      leaf process-status {
        type process-status-id;
      }
    }
  }

}
