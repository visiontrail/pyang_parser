module flexoran-5gnr-modules {
    namespace "http://certusnet.com.cn/flexoran/oam/flexoran-5gnr-modules";
    prefix oran5gmo;

    import flexoran-rru-manager {
        prefix rrumgr;
    }

    import flexoran-fap-service-mgr {
        prefix fapmgr;
    }

    import flexoran-alarm-manager {
        prefix almmgr;
    }

    import flexoran-alarms-profile {
        prefix almsprof;
    }

    import flexoran-gnb-mgr {
        prefix gnbmgr;
    }

    import flexoran-deviceinfo {
        prefix devinfo;
    }

    organization "certusnet";
    description "this module defines oam main module";

    container flexoran-5gnr {

        container cell-manager {
            // 符合tr069标准北向接口
            uses fapmgr:fap-service;
        }

        container rru-manager {
            // 私有管理模板
            uses rrumgr:o-ru-manager;
        }

        container gnb-manager {
            // 私有管理模板
            uses gnbmgr:gnb-manager;
        }

        container alarm-manager {
            // 私有管理模板
            uses almmgr:active-alarm-list;
        }

        container device-info {
            // tr069 DeviceId
            uses devinfo:device-info;
        }
    }

}
