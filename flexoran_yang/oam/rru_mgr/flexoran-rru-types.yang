module flexoran-rru-types {
    yang-version 1.1;
    namespace "http://certusnet.com.cn/flexoran/oam/flexoran-rru-types";
    prefix rrutype;

    organization "CertusNet";
    description "This module defines oam RRU Type manager.";

    feature optional {
        description "The auto-generated node is std::optional type.";
    }

    typedef rru-type {
        type enumeration {
            enum RRU-TYPE1 {
                description
                    "RRU-TYPE1";
            }
            enum RRU-TYPE2 {
                description
                    "RRU-TYPE1";
            }
        }
    }

    typedef eu-type {
        type enumeration {
            enum EU-TYPE1 {
                description
                    "EU-TYPE1";
            }
            enum EU-TYPE2 {
                description
                    "EU-TYPE1";
            }
        }
    }

    typedef txrx-status {
        type enumeration {
            enum TX {
                description
                    "tx";
            }
            enum RX {
                description
                    "rx";
            }
            enum TXRX {
                description
                    "rx";
            }
        }
    }
}
