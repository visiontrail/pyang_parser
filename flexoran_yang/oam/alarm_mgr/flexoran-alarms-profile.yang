module flexoran-alarms-profile {
  yang-version 1.1;
  namespace "http://certusnet.com.cn/flexoran/oam/flexoran-alarms-profile";
  prefix "almsprof";

  import ietf-yang-types {
    prefix yang;
    reference
      "RFC 6991: Common YANG Data Types.";
  }
  import tailf-common { prefix tailf; }

  organization "CertusNet 5G NR";
  contact 
    "
      Editor: Guoliang
              <mailto:guol@certusnet.com.cn>
    ";

  description
    "base on ietf-alarms.yang";
  
  revision 2019-11-21 {
      description "Initial revision.";
  }

  typedef severity {
    type enumeration {
      enum critical {
        value 1;
        description
          "The 'major' severity level indicates that a service
           terminated.  This level SHOULD be avoided.";
      }
      enum major {
        value 2;
        description
          "The 'major' severity level indicates that a service
           affecting condition has developed and an urgent corrective
           action is required.  Such a severity can be reported, for
           example, when there is a severe degradation in the
           capability of the resource and its full capability must be
           restored.";
          
      }
      enum minor {
        value 3;
        description
          "The 'minor' severity level indicates the existence of a
           non-service affecting fault condition and that corrective
           action should be taken in order to prevent a more serious
           (for example, service affecting) fault.  Such a severity
           can be reported, for example, when the detected alarm
           condition is not currently degrading the capacity of the
           resource.";
      }
      enum warning {
        value 4;
        description
           "The 'warning' severity level indicates the detection of a
           potential or impending service affecting fault, before any
           significant effects have been felt.  Action should be
           taken to further diagnose (if necessary) and correct the
           problem in order to prevent it from becoming a more
           serious service affecting fault.";
      }
    }
    description
      "The severity level of the alarm.  Note well that value 'clear'
       is not included.  If an alarm is cleared or not is a separate
       boolean flag.";
  }

  /* 告警类型 */
  typedef alarm-type-id {
    type enumeration {
      enum communication;
      enum service-quality;
      enum handling-error;
      enum device;
      enum environment;
    }
  }

  /*告警分类扩展*/
  typedef alarm-source-entity {
    type enumeration {
      enum cu;
      enum du;
      enum board;
      enum gNB;
      enum rru;
      enum processor;
      enum clock;
    }
    
    description
      "The definition of alarm qualifiers is considered being part of
       the instrumentation and out of scope for this module.  An
       empty string is used when this is part of a key.";
  }

  grouping alarm-msgheader {
    leaf source-level-1 {
      type uint8;
    }
    leaf source-level-2 {
      type uint8;
    }
  }

  grouping alarm-msg {
    leaf alarm-no {
      type uint32;
    }
    leaf alarm-value {
      type uint8;
    }
    leaf clear-flag {
      type boolean;
    }
    leaf alarm-content {
      type string;
    }
  }

  grouping alarm-struct {
    leaf alarm-no {
      type uint16;
    }
    leaf alarm-description {
      type string;
    }
    list alarm-attach-cause {
      key cause-no;

      leaf cause-no {
        type uint32;
      }

      leaf attach-cause-description {
        type string;
      }
    }
    leaf alarm-type {
      type alarm-type-id;
      description
          "Alarm type for all module in device.";
    }
    leaf alarm-severity {
      type severity;
      description
          "Alarm summary for this severity level.";
    }
    leaf alarm-source {
      type alarm-source-entity;
      description "alarm source";
    }
    leaf alarm-influence-equipment {
      type string;
      description
          "alarm influence equipment";
    }
    leaf alarm-influence-progress {
      type string;
      description
          "alarm influence progress";
    }
    leaf alarm-treatment {
      type string;
    }
  }

  grouping flexoran-alarms {
    description
      "flexoran-alarms cantaine local alarm profile and alarm message.";

    // 本地告警表
    list alarm-profile {
      key alarm-no;
      description
        "This list is used to assign further information or
         configuration for each alarm type.";
      uses alarm-struct;
    }
  }

  // Radisys <--> OAM 告警消息
  grouping alarm-oam-cudu-msg {
    list alarm-msgs {
      description
        "alarm message (CU and DU OAM Agent <--> OAM) and alarm report history";
      key "source-level-1 source-level-2 alarm-no";
      uses alarm-msgheader;
      uses alarm-msg;
    }
  }

  container alarms {
    uses flexoran-alarms;
  }
  
  
}
