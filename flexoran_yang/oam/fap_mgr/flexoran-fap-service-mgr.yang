module flexoran-fap-service-mgr {
    namespace "http://certusnet.com.cn/flexoran/oam/flexoran-fap-service-mgr";
    prefix fapmgr;

    import tailf-common { prefix tailf; }
    
    organization "CertusNet";
    contact 
    "
      Editor: Guoliang
              <mailto:guol@certusnet.com.cn>
    ";
    description "This module defines fap service(Femto Access Point service).";

    typedef cell-type-t {
        type enumeration {
            enum "SUB1G";
            enum "SUB6G";
            enum "ABOVE6G";
        }
    }
    
    grouping fap-service {
        list fap-services {
            description "fap services";
            tailf:info "小区信息";
            tailf:snmp-name fap-services;
            
            key fap-service;

            leaf fap-service {
                type uint32;
                description "Femto Access Point (also means cell in gNB) service";
                tailf:info "小区信息索引";
                tailf:snmp-name fap-service;
            }

            // 小区闭塞 5GC参数管理 基站PLMN参数列表 广播参数管理
            container cell-config {

                description "cell config";
                tailf:info "小区信息配置";
                tailf:snmp-name cell-config;
                
                leaf CellBarred {
                    type boolean;
                    default true;
                    description "cell barred(true) or unbarred(false).";
                    tailf:info "小区闭塞（true）和解闭塞（false）操作";
                    tailf:snmp-name CellBarred;
                    // Device.Services.FAPService.{i}.CellConfig.NR.RAN.CellRestriction.CellBarred
                }
                
                leaf EmergencyAreaID {
                    type uint8 {
                        range "0..7" {
                            error-message "EmergencyAreaID Value Should be in Between 1 to 16.";    
                        }
                    }
                    description "Emergency zone ID(3bit)";
                    tailf:info "突发事件区域ID(3bit)";
                    tailf:snmp-name EmergencyAreaID;
                    // Device.Services.FAPService.{i}.CellConfig.NR.5GC.EmergencyAreaID
                }

                leaf tac {
                    type uint32 {
                        range "0..16777215" {
                            error-message "tac Value Should be in Between 1 to 16777215.";    
                        }
                    }
                    description "Tracking area code, TAC(24bit)";
                    tailf:info "跟踪区代码，TAC(24bit)";
                    tailf:snmp-name tac;
                    // Device.Services.FAPService.{i}.CellConfig.NR.5GC.TAC
                }

                list PLMNLists {
                    description "a list of PLMN-Id-List, PLMN-Id= Mobile Country Codes (MCC)|| Mobile Network Codes(MNC) ";
                    tailf:info "PLMN-Id-List列表，PLMN-Id = 移动国家代码（MCC） + 移动网络代码（MNC）";
                    tailf:snmp-name PLMNLists;
                    key PLMNLists-index;

                    leaf PLMNLists-index {
                        type uint32;
                        description "key of plmnlists";
                    }

                    list PLMNList {
                        description "a list of PLMN-Id-List, PLMN-Id= Mobile Country Codes (MCC)|| Mobile Network Codes(MNC) ";
                        key PLMNList-index;

                        leaf PLMNList-index {
                            type uint32;
                            description "key of plmnlists";
                        }

                        leaf PLMN-ID {
                            type string;
                            description "plmnid";
                            tailf:info "公共陆地移动网ID";
                            tailf:snmp-name PLMN-ID;
                            // Device.Services.FAPService.{i}.CellConfig.NR.5GC.PLMNList{i}.{i}.PLMNID
                        }

                        leaf CellReservedForOperatorUse {
                            type boolean;
                            description "cell reserved For Operator";
                            tailf:info "小区是否预留标识";
                            tailf:snmp-name CellReservedForOperatorUse;
                            // Device.Services.FAPService.{i}.CellConfig.NR.5GC.PLMNList{i}.{i}.CellReservedForOperatorUse
                        }
                    }

                    
                }

                leaf MultiBandInfoListSIB1 {
                    type uint16 {
                        range "1..1024" {
                            error-message "MultiBandInfoListSIB1 Value Should be in Between 1 to 1024.";    
                        }
                    }
                    description "Multiband indication parameters in SIB1";
                    tailf:info "SIB1中多频段指示参数 1 .. 1024";
                    tailf:snmp-name MultiBandInfoListSIB1;
                    // Device.Services.FAPService.{i}.CellConfig.SysInfoCtrlParam.MultiBandInfoListSIB1
                }

                leaf MultiBandInfoListSIB5 {
                    type uint8 {
                        range "1..64" {
                            error-message "MultiBandInfoListSIB5 Value Should be in Between 1 to 64.";
                        }
                    }
                    description "Multiband indication parameters in SIB5";
                    tailf:info "SIB5中多频段指示参数 1..64";
                    tailf:snmp-name MultiBandInfoListSIB5;
                    // Device.Services.FAPService.{i}.CellConfig.SysInfoCtrlParam.MultiBandInfoListSIB5
                }

                // 小区参数管理
                container cell-parameter {
                    description "cell parameter manager";
                    tailf:info "小区参数管理";
                    tailf:snmp-name cell-parameter;

                    leaf gNBId {
                        type uint64;
                        description "gNBId";
                        tailf:info "gNBId";
                        tailf:snmp-name gNBId;
                        // Device.Services.FAPService.{i}.CellConfig.NR.RAN.Common.gNBId
                    }

                    leaf gNBName {
                        type string;
                        description "gNBName";
                        tailf:info "gNB名称";
                        tailf:snmp-name gNBName;
                        // Device.Services.FAPService.{i}.CellConfig.NR.RAN.Common.gNBName
                    }

                    leaf cellType {
                        type cell-type-t;
                        description "cell Type";
                        tailf:info "小区类型";
                        tailf:snmp-name cellType;
                        // Device.Services.FAPService.{i}.CellConfig.NR.RAN.Common.cellType
                    }

                    leaf cellReservedForOtherUse {
                        type boolean;
                        description "Plot reserved identification of the main switch";
                        tailf:info "小区预留标识总开关";
                        tailf:snmp-name cellReservedForOtherUse;
                        // Device.Services.FAPService.{i}.CellConfig.NR.NGC.cellReservedForOtherUse
                    }

                    leaf NRARFCNDL {
                        type string;
                        description "DL NRARFCN";
                        tailf:info "NR绝对无线频道编号(下行)";
                        tailf:snmp-name NRARFCNDL;
                        // Device.Services.FAPService.{i}.CellConfig.NR.RAN.RF.NRARFCNDL
                    }

                    leaf PhyCellID {
                        type string;
                        description "PCI";
                        tailf:info "小区物理ID";
                        tailf:snmp-name PhyCellID;
                        // Device.Services.FAPService.{i}.CellConfig.NR.RAN.RF.PhyCellID
                    }

                    leaf DLBandwidth {
                        type string;
                        description "DL Bandwidth";
                        tailf:info "小区下行带宽";
                        tailf:snmp-name DLBandwidth;
                        // Device.Services.FAPService.{i}.CellConfig.NR.RAN.RF.DLBandwidth
                    }
                    
                    leaf ULBandwidth {
                        type string;
                        description "UL Bandwidth";
                        tailf:info "小区上行带宽";
                        tailf:snmp-name ULBandwidth;
                        // Device.Services.FAPService.{i}.CellConfig.NR.RAN.RF.ULBandwidth
                    }

                    leaf PSCHPowerOffset {
                        type string;
                        description "PSCH Power Offset";
                        tailf:info "PSCH功率偏移";
                        tailf:snmp-name PSCHPowerOffset;
                        // Device.Services.FAPService.{i}.CellConfig.NR.RAN.RF.PSCHPowerOffset
                    }

                    leaf NRARFCNUL {
                        type string;
                        description "UL NRARFCN";
                        tailf:info "NR绝对无线频道编号(上行)";
                        tailf:snmp-name NRARFCNUL;
                        // Device.Services.FAPService.{i}.CellConfig.NR.RAN.RF.NRARFCNUL
                    }

                    leaf FreqBandIndicator {
                        type uint16 {
                            range "1..1024" {
                                error-message "FreqBandIndicator Value Should be in Between 1 to 1024.";    
                            }
                        }
                        description "FreqBand Indicator";
                        tailf:info "小区频带指示";
                        tailf:snmp-name FreqBandIndicator;
                        // Device.Services.FAPService.{i}.CellConfig.NR.RAN.RF.FreqBandIndicator
                    }

                    leaf SsPBCHBlockPower {
                        type int8 {
                            range "-60..50" {
                                error-message "SsPBCHBlockPower Value Should be in Between -60 to 50.";    
                            }
                        }
                        description "SSB Block Power";
                        tailf:info "SSB Block功率值";
                        tailf:snmp-name SsPBCHBlockPower;
                        // Device.Services.FAPService.{i}.CellConfig.NR.RAN.RF.SsPBCHBlockPower
                    }
                }

                // CU参数？？核心网？？
                // list TA {

                // }

            }

            // 基站运行状态参数
            container cell-state {
                description "cell(fap) state";
                tailf:info "小区状态";
                tailf:snmp-name cell-state;
                config false;

                leaf AdminState {
                    type boolean;
                    description "cell(fap) management status";
                    tailf:info "小区管理状态";
                    tailf:snmp-name AdminState;
                    // Device.Services.FAPService.{i}.FAPControl.NR.AdminState
                }

                leaf OpState {
                    type boolean;
                    description "cell(fap) operating state";
                    tailf:info "小区运行状态";
                    tailf:snmp-name OpState;
                    // Device.Services.FAPService.{i}.FAPControl.NR.OpState
                }

                leaf RFTxStatus {
                    type boolean;
                    description "cell(fap) frequency status";
                    tailf:info "基站射频状态";
                    tailf:snmp-name RFTxStatus;
                    // Device.Services.FAPService.{i}.FAPControl.NR.RFTxStatus
                }
            }

            // Xn连接地址？？？CU参数？？

            // AMF地址  CU参数？？
            list AMFPoolConfigParam {
                key AMFName;
                description " Access and Mobility Management Function";
                tailf:info "接入和移动管理功能";

                leaf AMFName {
                    type string;
                    description "";
                    // Device.Services.FAPService.{i}.CellConfig.NR.AMFPoolConfigParam.{i}.AMFName
                }

                leaf PLMNID {
                    type string;
                    description "";
                    // Device.Services.FAPService.{i}.CellConfig.NR.AmfPoolConfigParam.{i}.PLMNID
                }

                leaf AMFRegionID {
                    type string;
                    description "";
                    // Device.Services.FAPService.{i}.CellConfig.NR.AmfPoolConfigParam.{i}.AMFRegionID
                }

                leaf AMFSetID {
                    type string;
                    description "";
                    // Device.Services.FAPService.{i}.CellConfig.NR.AmfPoolConfigParam.{i}.AMFSetID
                }

                leaf AMFPointer {
                    type string;
                    description "";
                    // Device.Services.FAPService.{i}.CellConfig.NR.AmfPoolConfigParam.{i}.AMFPointer
                }

                leaf RelativeAMFCapacity {
                    type uint8 {
                        range "0..255" {
                            error-message "tac Value Should be in Between 1 to 255.";    
                        }
                    }
                    description "Relative AMF Capacity.";
                    // Device.Services.FAPService.{i}.CellConfig.NR.AMFPoolConfigParam.{i}.RelativeAMFCapacity
                }

                leaf AMFIP1 {
                    type string;
                    description "";
                    // Device.Services.FAPService.{i}.CellConfig.NR.AmfPoolConfigParam.{i}.AMFIP1
                }

                leaf AMFIP2 {
                    type string;
                    description "";
                    // Device.Services.FAPService.{i}.CellConfig.NR.AmfPoolConfigParam.{i}.AMFIP2
                }
            }
            
            container Capabilities {
                description "cell(fap) Capabilities config";
                tailf:info "小区能力配置";
                tailf:snmp-name Capabilities;

                leaf MaxTxPower {
                    config false;
                    type uint32;
                    description "Max Tx Power";
                    tailf:info "小区最大发射功率";
                    tailf:snmp-name MaxTxPower;
                    // Device.Services.FAPService.{i}.Capabilities.MaxTxPower
                }

                leaf UeInactiveTimer {
                    type uint32;
                    description "Connection UE inactive timer.";
                    tailf:info "连接态UE不活动定时器时长";
                    tailf:snmp-name UeInactiveTimer;
                    // Device.Services.FAPService.{i}.Capabilities.NR.UeInactiveTimer
                }

                leaf SupportRRCNumbers {
                    config false;
                    type uint32;
                    description "supports RRC connection to the maximum number of users in the same time.";
                    tailf:info "同时支持RRC连接最大用户数";
                    tailf:snmp-name SupportRRCNumbers;
                    // Device.Services.FAPService.{i}.Capabilities.NR.MaxUEsServed
                }

                leaf SupportActiveRRCNumbers {
                    config false;
                    type uint32;
                    description "RRC is supported to activate the maximum number of users in the same time";
                    tailf:info "同时支持RRC激活最大用户数";
                    tailf:snmp-name SupportActiveRRCNumbers;
                    // Device.Services.FAPService.{i}.Capabilities.NR.SupportActiveRRCNumbers
                }
            }

        }
    }

    // OAM <--> DU 间消息，小区建立结果
    grouping oam_du_cell_msg {
        container oam_du_cell_active_ret_ind {
            leaf cell_state {
                type enumeration {
                    enum "SUCCESS";
                    enum "INCOMPLETE";
                    enum "FAIL";
                }
            }

        }
    }
}
