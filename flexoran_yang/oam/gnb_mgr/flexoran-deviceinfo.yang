/*
 * 通信设备通用信息模型
*/
module flexoran-deviceinfo {
    namespace "http://certusnet.com.cn/flexoran/oam/flexoran-deviceinfo";
    prefix devinfo;

    import tailf-common { prefix tailf; }
    import ietf-yang-types { prefix yang; }
    organization "CertusNet";
    contact
    "
      Editor: Guoliang
              <mailto:guol@certusnet.com.cn>
    ";
    description "This module defines fap service(Femto Access Point service).";

    grouping device-info {

        container base-info {

            tailf:callpoint "device-base-info";
            config false;

            // 制造商oui
            leaf manufactureroui {
                type string;
                description "indicates whether serial number is included on the equipment's label";
                tailf:info "制造商OUI";
                tailf:snmp-name manufactureroui;
            }

            // 制造商
            leaf manufacturer {
                type string;
                description "manufacturer";
                tailf:info "制造商名称";
                tailf:snmp-name manufacturer;
            }

            // 设备型号
            leaf modelname {
                type string;
                description "modelname";
                tailf:info "设备型号";
                tailf:snmp-name modelname;
            }

            // 序列号
            leaf serial-number {
                type string;
                description "device serial-number";
                tailf:info "设备序列号";
                tailf:snmp-name serial-number;
            }

            // 硬件版本
            leaf hardwareversion {
                type string;
                description "device hardware version";
                tailf:info "设备的硬件版本";
                tailf:snmp-name hardwareversion;
            }

            // 软件版本
            leaf softwareversion {
                type string;
                description "device software version";
                tailf:snmp-name softwareversion;
            }

            // 硬件平台
            leaf hardwareplatform {
                type string;
                description "device hardwareplatform";
                tailf:snmp-name hardwareplatform;
            }

            // 附加硬件版本
            leaf additionalhardwareversion {
                type string;
                description "device additionalhardwareversion";
                tailf:snmp-name additionalhardwareversion;
            }

            // 附加软件版本
            leaf additionalsoftwareversion {
                type string;
                description "device additionalsoftwareversion";
                tailf:snmp-name additionalsoftwareversion;
            }

            // 供应商代号
            leaf provisioningcode {
                type string;
                description "device provisioningcode";
                tailf:snmp-name provisioningcode;
            }

            // 产品分类
            leaf productclass {
                type string;
                description "device productclass";
                tailf:snmp-name productclass;
            }

            // 运行时间
            leaf uptime {
                type uint32;
                description "device uptime";
                tailf:snmp-name uptime;
            }

            // 3gpp协议版本
            leaf dev-3gppspecversion {
                type string;
                description "device 3gppspecversion";
                tailf:snmp-name dev3gppspecversion;
            }

            // 首次使用日期,TODO:需要自定义时间类型
            leaf firstusedate {
                type string;
                description "device firstusedate";
                tailf:snmp-name firstusedate;
            }
        }

        container extern-info {
            // 设备友好名
            leaf equipfriendlyname {
                type string;
                default "CertusNet";
                description "device manufacturer name";
                tailf:snmp-name equipfriendlyname;
            }

            leaf url {
                type string;
                default "http://certusnet.com.cn";
                description "device url";
                tailf:snmp-name url;
            }

            leaf param-key {
                type string;
                default "";
                description "device param-key";
                tailf:snmp-name param-key;
            }

            leaf period {
                type int32;
                default 100;
                description "device period";
                tailf:snmp-name int32;
            }
        }

        container Management-Server {

			// ACS使用CWMP连接ACS的URL。格式必须为合法的HTTP/HTTPS的形式。
			leaf URL {
				type string {
				  length "1..255";
				}
                default "http://192.168.10.120:8768/inform";
				description "ACS uses CWMP to connect to the ACS URL. Format must be in the form of legitimate HTTP/HTTPS.";
				tailf:info "网管服务器URL";
				tailf:snmp-name	URL;
			}

			// ACS使用CWMP连接基站时使用的认证用户名。仅用于基站的基于HTTP的认证。
			leaf Username {
				type string {
				  length "1..255";
				}
                default "test";
				description "The authentication user name that ACS uses to connect to the base station using CWMP. HTTP based authentication for base stations only.";
				tailf:info "连接用户名";
				tailf:snmp-name	Username;
			}

			// 基站使用CWMP连接ACS时使用的认证密码。仅用于基站的基于HTTP的认证。读取时返回一个空字符串.
			leaf Password {
				type string {
				  length "1..255";
				}
                default "test";
				description "The authentication password used by the base station to connect ACS using CWMP. HTTP based authentication for base stations only. An empty string is returned when reading.";
				tailf:info "连接密码";
				tailf:snmp-name	Password;
			}

			// 基站是否必须利用Inform方法调用定时向服务器端发送基站信息。当PeriodicInformEnable=true时，PeriodicInformInterval才起作用
			leaf PeriodicInformEnable {
				type boolean;
				description "Whether the base station must use the information method call to send the base station information to the server. Periodicinforminterval only works when periodicinformenable = true.";
				tailf:info "连接使能开关";
				tailf:snmp-name	PeriodicInformEnable;
			}

			leaf PeriodicInformTime {
				type yang:date-and-time;
				description "2012-12-11T19:15:00";
				tailf:info "上报周期";
				tailf:snmp-name	PeriodicInformTime;
			}

			// 在PeriodicInformEnable为真时，基站必须尝试连接ACS并调用Inform方法的时间间隔。当PeriodicInformEnable=true才生效
			leaf PeriodicInformInterval {
				type int32 {
					range "1 .. 65535";
				}
				description "When periodicinformenable is true, the interval at which the base station must attempt to connect to ACS and call the information method. Valid when periodicinformenable = true.";
				tailf:info "周期上报时间间隔";
				tailf:snmp-name	PeriodicInformInterval;
			}

			// 来自于服务器的最新的 SetParameterValues，AddObject 或 DeleteObject 方法调用的 ParameterKey 自变量数值。如果没有此类调用，此数值为空。
			leaf ParameterKey {
				config false;
				type string {
					length "0..32";
				}
				description "The parameter key argument value of the latest setparametervalues, addObject or deleteobject method call from the server. If there is no such call, the value is empty.";
				tailf:info "键值";
				tailf:snmp-name	ParameterKey;
			}

			// ACS向基站发起连接请求通知时所使用的HTTPURL。其形式如下：http://host:port/SOAP/HNBServlet?a=1的"主机"部分可以是基站管理接口的IP地址，用以替代域名。
			leaf ConnectionRequestURL {
				config false;
				type string {
					length "1..255";
				}
				description "The HTTP URL used by ACS to send a connection request notification to the base station. Its form is as follows:  http://host:port/SOAP/HNBServlet?a=1 the 'host' part ofcan be the IP address of the base station management interface to replace the domain name.";
				tailf:info "连接请求URL";
				tailf:snmp-name	ConnectionRequestURL;
			}

			// ACS向基站发起连接请求时，鉴权过程使用的用户名。
			leaf ConnectionRequestUsername {
				type string {
				  length "1..255";
				}
				description "The user name used by the authentication process when the ACS initiates a connection request to the base station.";
				tailf:info "连接请求用户名";
				tailf:snmp-name	ConnectionRequestUsername;
			}

			// ACS向基站发起连接请求时，鉴权过程使用的密码。在被读取时，该参数会忽略实际值而返回一个空字符串。
			leaf ConnectionRequestPassword {
				type string {
				  length "1..255";
				}
				description "The password used by the authentication process when the ACS initiates a connection request to the base station. When read, this parameter ignores the actual value and returns an empty string.";
				tailf:info "连接请求密码";
				tailf:snmp-name	ConnectionRequestPassword;
			}

			// UDP连接请求地址
			leaf UDPConnectionRequestAddress {
				config false;
				type string {
				  length "1..255";
				}
				description "UDP connection request address.";
				tailf:info "UDP连接请求地址";
				tailf:snmp-name	UDPConnectionRequestAddress;
			}

			// STUN使能开关
			leaf STUNEnable {
				type boolean;
				description "STUN enable switch (0=false,1=true).";
				tailf:info "STUN使能开关";
				tailf:snmp-name	STUNEnable;
			}

			// STUN服务器地址
			leaf STUNServerAddress {
				type string {
				  length "1..255";
				}
				description "STUN server address.";
				tailf:info "STUN服务器地址";
				tailf:snmp-name	STUNServerAddress;
			}

			// STUN服务器端口
			leaf STUNServerPort {
				type uint16;
				description "STUN server Port.";
				tailf:info "STUN服务器端口";
				tailf:snmp-name	STUNServerPort;
			}

			// STUN用户名
			leaf STUNUsername {
				type string {
				  length "1..255";
				}
				description "STUN Username.";
				tailf:info "STUN用户名";
				tailf:snmp-name	STUNUsername;
			}

			// STUN密码
			leaf STUNPassword {
				type string {
				  length "1..255";
				}
				description "STUN Password.";
				tailf:info "STUN密码";
				tailf:snmp-name	STUNPassword;
			}

			// STUN最大生存周期
			leaf STUNMaximumKeepAlivePeriod {
				type int32 {
					range "-1 .. 65535";
				}
				description "STUN Maximum Keep Alive Period.";
				tailf:info "STUN最大生存周期";
				tailf:snmp-name	STUNMaximumKeepAlivePeriod;
			}

			// STUN最小生存周期
			leaf STUNMinimumKeepAlivePeriod {
				type uint16;
				description "STUN Minimum Keep Alive Period.";
				tailf:info "STUN最小生存周期";
				tailf:snmp-name	STUNMinimumKeepAlivePeriod;
			}

			// NAT转换地址
			leaf NATDetected {
				config false;
				type boolean;
				description "NAT Detected (0=false,1=true).";
				tailf:info "NAT转换地址";
				tailf:snmp-name	NATDetected;
			}
		}
    }
}
