module o-ran-cpri-delay-management {
  yang-version 1.1;
  namespace "urn:o-ran:cpri-delay:1.0";
  prefix "o-ran-cpri-delay";

  organization "O-RAN Alliance";

  contact
    "www.o-ran.org";

  description
    "This module covers off aspects of O-DU to O-RU delay management,
    including config data related to O-RU transmission and reception
    windows.

    Copyright 2019 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2019-11-18" {
    description
      "version 1.0.0

      1) add CPRI time delay yang module";

    reference "ORAN-WG4.M.0-v01.00";
  }

  container delay-management {
    description "top level tree covering off O-DU to O-RU delay management";

    list ports-delay {
      key "port-name";
      description
        "Segmentation measurement result statistics.";

      leaf port-name {
        type leafref {
          path '/if:interfaces/if:interface/if:name';
        }
        description
          "O-RAN interfaces use a reference to a interface component.";
      }

      container ru-delay-profile {
        config false;
        description "container for O-RU delay parameters";

        leaf access-Ul-TimeDelay {
          type uint32;
          units "ns";
          description "RRU Access Main DownLink Time Delay ";
        }

        leaf access-Dl-TimeDelay {
          type uint32;
          units "ns";
          description "RRU Access Main UpLink Time Delay ";
        }

      }
    }
  }

  rpc cpri-periodic-delay-measurement {
    description
      "Rpc to support communication between O-DU and O-RU periodic dalay measurement";

    input {
      leaf fiber-number {
        type uint8 {
          range "0 .. 1 ";
        }
        mandatory true;
        description
          "The delay measurement is performed on the primary fiber and the 
           secondary/standby fiber";
      }
    }

    output {
      leaf fiber-number {
        type uint8 {
          range "0 .. 1 ";
        }
        mandatory true;
        description
          "The delay measurement is performed on the primary fiber and the 
           secondary/standby fiber";
      }

      leaf Toffset {
        type uint32;
        mandatory true;
        units "ns";

        description
          "Toffset";
      }

      leaf TBdelay-DL {
        type uint32;
        mandatory true;
        units "ns";

        description
          "TBdelay DL";
      }

      leaf TBdelay-UL {
        type uint32;
        mandatory true;
        units "ns";

        description
          "TBdelay UL";
      }

      leaf T2a {
        type uint32;
        mandatory true;
        units "ns";

        description
          "T2a";
      }

      leaf Ta3 {
        type uint32;
        mandatory true;
        units "ns";

        description
          "Ta3";
      }

      leaf N {
        type uint32;
        mandatory true;
        units "ns";

        description
          "N";
      }
    }
  }


  rpc cpri-delay-configuration {
    description
      "Rpc to support communication between O-DU and O-RU cpri delay configuration";

    input {
      leaf fiber-number {
        type uint8 {
          range "0 .. 1 ";
        }
        mandatory true;
        description
          "The delay measurement is performed on the primary fiber and the 
           secondary/standby fiber";
      }

      leaf t12 {
        type uint32;
        mandatory true;
        units "ns";

        description
          "t12";
      }

      leaf t34 {
        type uint32;
        mandatory true;
        units "ns";

        description
          "t34";
      }

      leaf DL-Offset-a {
        type uint32;
        mandatory true;
        units "tc";

        description
          "DL Offset a";
      }

      leaf DL-cal {
        type uint32;
        mandatory true;
        units "ns";

        description
          "DL cal o-ru";
      }

      leaf UL-cal {
        type uint32;
        mandatory true;
        units "ns";

        description
          "UL cal o-ru";
      }
    }

    output {
      leaf fiber-number {
        type uint8 {
          range "0 .. 1 ";
        }
        mandatory true;
        description
          "The delay measurement is performed on the primary fiber and the 
           secondary/standby fiber";
      }

      leaf configuration-result {
        type boolean;
        mandatory true;
        units "ns";

        description
          "configuration result";
      }
    }
  }

}
